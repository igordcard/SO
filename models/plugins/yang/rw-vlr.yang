/*
 * 
 *   Copyright 2016 RIFT.IO Inc
 *
 *   Licensed under the Apache License, Version 2.0 (the "License");
 *   you may not use this file except in compliance with the License.
 *   You may obtain a copy of the License at
 *
 *       http://www.apache.org/licenses/LICENSE-2.0
 *
 *   Unless required by applicable law or agreed to in writing, software
 *   distributed under the License is distributed on an "AS IS" BASIS,
 *   WITHOUT WARRANTIES OR CONDITIONS OF ANY KIND, either express or implied.
 *   See the License for the specific language governing permissions and
 *   limitations under the License.
 *
 *
 */

module rw-vlr
{
  namespace "http://riftio.com/ns/riftware-1.0/rw-vlr";
  prefix "rw-vlr";

  import mano-types {
    prefix "manotypes";
  }

  import vlr {
    prefix "vlr";
  }

  import rw-cloud {
    prefix "rwcloud";
  }

  import ietf-yang-types {
    prefix "yang";
  }

  revision 2015-09-30 {
    description
      "Initial revision. This YANG file augments
       the base MANO VNFD";
    reference
      "Derived from earlier versions of base YANG files";
  }

  augment /vlr:vlr-catalog/vlr:vlr {
    leaf cloud-account {
      description
        "The cloud account to use when requesting resources for
         this vlr";
      type leafref {
        path "/rwcloud:cloud/rwcloud:account/rwcloud:name";
      }
    }
    leaf om-datacenter {
      description
          "Openmano datacenter name to use when instantiating
          the network service.  This is only used when openmano
          is selected as the cloud account.  This should be superceded
          by multiple cloud accounts when that becomes available.";
      type string;
    }


    leaf network_pool {
      description "The network pool the resource was allocated from.";
      type string;
    }

    leaf assigned-subnet {
      description "Subnet added for the VL";
      type string;
    }

    leaf operational-status-details {
      description
        "The error message in case of a failed VLR operational status";
      type string;
    }
  }
}

// vim: sw=2
